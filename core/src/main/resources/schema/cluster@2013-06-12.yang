module cluster {
    namespace "urn:cluster:yang";
    prefix "cluster";

    import bigdb {
        prefix bigdb;
        revision-date 2012-10-12;
    }
    import ietf-inet-types {
        prefix "ietf";
        revision-date "2010-09-24";
    }

    description "Schema for managing a controller cluster";

    organization "www.openflowhub.org";

    revision "2013-06-12" {
        description "Initial revision";
    }

    typedef node-id {
        description "A node ID in a controller cluster";
        type uint16 {
            range "1 .. 32767";
        }
    }

    container cluster {
        config false;
        bigdb:data-source "controller-data-source";

        container config {
            bigdb:cascade "false";
            description "Pseudo-RPC calls to set up clustering";
            
            leaf local-node-port {
                description "The port to use for cluster communication.  This 
                    value is read/write.";
                type ietf:port-number;
            }
            
            leaf local-node-iface {
                description "The interface name to use for cluster communication.
                    The IP address for the node will be derived from the IP 
                    address configured on this interface.  This value is 
                    read/write.";
                type string {
                    length "1 .. 32";
                }
            }
            
            leaf local-node-host {
                description "The ip address or hostname to use for cluster 
                    communication. This value is read/write; this value 
                    overrides local-node-iface";
                type ietf:domain-name;
            }
            
            container local-node-auth {
                description "Cluster authentication configuration";
                leaf auth-scheme {
                    type enumeration {
                        enum no-auth;
                        enum challenge-response;
                    }
                }
                leaf keystore-path {
                    type string {
                        length "1 .. 1024";
                    }
                }
                leaf keystore-password {
                    type string {
                        length "1 .. 128";
                    }
                }

                leaf cluster-secret {
                    bigdb:cascade "false";
                    description "Base64-encoded version of the cluster secret 
                        used for challenge-response authentication.  Writing
                        an empty string to this value will cause a new random
                        128-bit secret to be generated";
                    type string {
                        length "0 .. 48";
                    }
                }
            }
            
            leaf local-domain-id {
                description "The domain ID of the local node.  This value
                    is read/write.";
                type node-id;
            }
            
            leaf seeds {
                description "Set the seeds list.  Note that this will only do
                    something if the node is not currently in a cluster, as a 
                    comma-separated list of host:port pairs.  This
                    value is write-only";
                
                type string {
                    length "0 .. 2048";
                }
            }
            
            leaf reseed {
                description "Set to true to trigger a reseed.  If you 
                    simultaneously change the IP of every node in the
                    cluster, the cluster may not automatically reform.
                    Run this command to cause it to rerun the bootstrap
                    process while retaining existing node IDs.  The node
                    will be put into its own local domain.  Note that this
                    will only do something useful if the seeds parameter
                    is updated with at least one cluster member. This is
                    write-only.";
                
                type boolean;
            }
            
            leaf delete-node {
                description "Delete a node from the cluster.  Note that if 
                    the node is still active it will rejoin automatically, so only
                    run this once the node has been disabled.";
                type node-id;
            }

            container new-election {
                description "Start a new leader election.  Normally this will happen
                    automatically, but you can force it to occur using this API call.";

                leaf rigged {
                    description "If you specify a rigged election, then the
                        node on which the election began will be the one to win, 
                        assuming it lives long enough to take office.";
                    type boolean;
                }
            }
        }
        
        container status {
            description "Read-only status information";
            
            list nodes {
                key "node-id";
                leaf node-id {
                    description "The node ID";
                    type node-id;
                }
                leaf domain-id {
                    description "The domain ID for this node";
                    type node-id;
                }
                leaf hostname {
                    description "The hostname/IP address used to connect
                        to this node for cluster communication";
                    type ietf:domain-name;
                }
                leaf port {
                    description "The port used to connect to this node 
                        for cluster communication";
                    type ietf:port-number;
                }
                leaf status {
                    description "Whether the node is currently connected
                        to this node";
                    type enumeration {
                        enum disconnected;
                        enum connected;
                    }
                }
            }
            
            leaf local-node-id {
                description "The node ID of the current node";
                type node-id;
            }

            container domain-leader {
                description "The node ID of the current domain leader in
                    the local node's domain.  This leaf will be missing if 
                    there is no current leader";
                leaf leader-id {
                    type node-id;
                }
            }
        }
    }
}
