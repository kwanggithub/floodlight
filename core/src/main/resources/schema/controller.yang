module controller {
    namespace org.projectfloodlight.db;
    prefix "c";
    
    description "Model for an OpenFlow controller";
    
    organization "www.openflowhub.org";
    
    typedef dpid {
        description "A colon-separated hex DPID string";
        type string {
            length min..32;
            pattern "[0-9a-fA-F]{2}(:[0-9a-fA-F]{2}){7}";
        }
    }
    
    typedef mac-address {
        description "A colon-separated hex MAC string";
        type string {
            pattern "[0-9a-fA-F]{2}(:[0-9a-fA-F]{2}){5}";
        }
    }
    
    typedef ip-address {
        description "A dotted decimal IP string";
        type string {
            pattern "([0-9]{1,3}\\.){3}[0-9]{1,3}";
        }
    }
    
    typedef date-time {
        description "Date string";
        type string {
            length "min..64";
            pattern "[0-9]+";
        }
    }
    
    typedef vlan-id {
        description "VLAN tag";
        type int16 {
            range 0..4096;
         }
    }
    
    container schemas {
        
        list hosts {
        
            // config false;
            key "mac";
            
            leaf mac {
                type mac-address;
                description "MAC Address";
            }
            
            leaf vlan {
                type vlan-id;
            }
            
            leaf last-seen {
                type date-time;
            }
            
            leaf-list aliases {
                description "Aliases for this host";
                type string;
                config true;
            }
            
            list attachment-points {
                key "id";
                
                leaf id {
                    type string;
                }
                
                leaf switch {
                    type dpid;
                }
                leaf inport {
                    type uint16 {
                        range "1..max";
                    }
                }
                leaf last-seen {
                    type date-time;
                }
                leaf error-status {
                    type string;
                }
            }
            
            list network-addresses {
            
                key "id";
                
                leaf id {
                    type string;
                }
                
                leaf ip {
                    type ip-address;
                }
                
                leaf last-seen {
                    type date-time;
                }
            }
        }
        
        list switches {
        
            // config false;
            key "dpid";
            
            leaf dpid {
                type dpid;
                description "Datapath ID of the switch";
            }
            leaf ip {
                type ip-address;
                description "IP address of switch";
            }
            leaf active {
                type boolean;
                description "Switch is actively connected to the controller";
            }
            leaf connected-since {
                type date-time;
            }
            leaf capabilities {
                type uint32;
            }
            leaf-list aliases {
                description "Aliases for the switch";
                type string;
                config true;
            }
            leaf core-switch {
                type boolean;
                config true;
            }
            
            list ports {
                leaf name {
                    type string;
                }
                leaf number {
                    type uint16 { range "1..max"; }
                }
                leaf hardware-address {
                    type mac-address;
                }
                leaf config-flags {
                    type uint32;
                }
                leaf state-flags {
                    type uint32;
                }
                leaf current-features {
                    type uint32;
                }
                leaf advertised-features {
                    type uint32;
                }
            }
        }
    }
}
