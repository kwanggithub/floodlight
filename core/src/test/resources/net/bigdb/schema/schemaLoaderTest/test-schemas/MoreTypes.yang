module MoreTypes {
    namespace net.bigdb;
    prefix "mt";
    import Types {
        prefix "t";
    }
    import Types {
        prefix "ot";
        revision-date "2012-08-01";
    }
    
    description "More common types";
    
    organization "Acme";
    
    typedef hex-string {
        type t:short-string {
            pattern "[0-9a-fA-F]*";
        }
    }
    
    typedef older-hex-string {
        type ot:short-string {
            pattern "[0-9a-fA-F]*";
        }
    }
}
