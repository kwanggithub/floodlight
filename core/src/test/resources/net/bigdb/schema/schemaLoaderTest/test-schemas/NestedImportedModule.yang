module NestedImportedModule {
    namespace net.bigdb;
    prefix "nim";
    import Types {
        prefix t;
    }
    import MoreTypes {
        prefix mt;
    }
    
    description "Test nested module importing";
    
    organization "Acme";
    
    container schemas {
        leaf test-int {
            type t:positive-integer;
        }
        leaf test-string {
            type mt:hex-string;
        }
    }
}
