module DiffDataNodeTest {
    namespace net.bigdb;
    prefix "ldnt";

    import bigdb {
        prefix bigdb;
    }

    description "Diff data node test schema";

    organization "BigDB Inc.";

    container container-test {
        leaf child1 {
            type int32;
        }
        leaf child2 {
            type int32;
        }
        leaf-list child3 {
            type string;
        }
        container child4 {
            leaf child4.1 {
                type string;
            }
            leaf child4.2 {
                type int32;
            }
        }
    }

    list list-test {
        key "child1 child2";
        leaf child1 {
            type string;
        }
        leaf child2 {
            type int32;
        }
        leaf child3 {
            type string;
        }
        container child4 {
            leaf child4.1 {
                type int32;
            }
            leaf child4.2 {
                type string;
            }
        }
    }
}
