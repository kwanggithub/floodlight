module NestedListTest {
    namespace net.bigdb;
    prefix "nlt";
    
    description "Nested list test model";
    
    organization "BigDB Inc.";
    
    extension data-source {
        argument data-source-name;
    }
    
    list outer-list {
        config false;
        nlt:data-source "nested-list";
        key id;
        leaf id { type string; }
        list middleList {
            nlt:data-source "nested-list";
            key id;
            leaf id { type string; }
            list innerList {
                nlt:data-source "nested-list";
                key id;
                leaf id { type string; }
            }
        }
    }
}
