module TypedefTest {
    /* Here's a multi-line comment.
       Another line.
    */
    namespace "net.bigdb";
    // Single line comment
    prefix "tt";
    typedef date-time-string {
        description "Date string";
        type string {
            length "min..64";
            pattern "[0-9]+";
        }
    }
    
    typedef vlan-integer {
        description "VLAN tag";
        type integer {
            range 0..4096;
         }
    }
    
    typedef range-test {
        type integer {
            range 0..31|35|44..60|100..max {
                description "Overly complicated range";
            }
        }
    }
}
