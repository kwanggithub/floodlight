module StringRestrictions {
    namespace org.projectfloodlight.db;
    prefix "mt";
    import Types {
        prefix "t";
    }
    import Types {
        prefix "ot";
        revision-date "2012-08-01";
    }
    
    description "More common types";
    
    organization "Acme";
    
    typedef hex-string {
        type t:short-string {
            pattern "[0-9a-fA-F]*";
        }
    }
    
    typedef older-hex-string {
        type ot:short-string {
            pattern "[0-9a-fA-F]*";
        }
    }
    container string-restriction-test {
        leaf test-hex-string {
            type older-hex-string {
                length 2..32;
            }
            default "5678FA";
        }
    }
}
