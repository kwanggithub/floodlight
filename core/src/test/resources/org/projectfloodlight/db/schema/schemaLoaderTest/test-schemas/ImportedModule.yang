module ImportedModule {
    namespace org.projectfloodlight.db;
    prefix "im";
    import Types {
        prefix t;
    }
    
    description "Test module importing";
    
    organization "Acme";
    
    container schemas {
        leaf test-int {
            type t:positive-integer;
        }
        leaf test-string {
            type t:short-string;
        }
    }
}
