module TypedefResolution {
    namespace org.projectfloodlight.db;
    prefix "mt";
    
    description "More typedef resolution tests.";
    
    organization "Acme";
    
    typedef type-1 {
        type type-3;
    }
    typedef type-3 {
        type type-2;
    }
    
    typedef type-2 {
        type enumeration {
            enum value2 {
                value 2;
            }
            enum value1 {
                value 1;
            }
            enum value4 {
                value 4;
            }
        }
    }
}
