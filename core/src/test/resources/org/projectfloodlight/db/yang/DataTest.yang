module DataTest {
    yang-version 1.0;
    namespace org.projectfloodlight.db;
    prefix "dt";
    organization "www.bigdb.net";
    contact "Paddy Huntington";
    description "Test module headers";
    reference "Test reference";

    container config-data {
        config true;
        leaf int1 {
            type int32;
            description "XYZ";
            mandatory true;
            status deprecated;
        }
        container subtree1 {
            leaf-list percentage1 {
                type uint8 {
                    range min..100 {
                        error-message "Percentage out of range";
                        description "Percentage";
                    }
                }
                description "ABC";
                min-elements 1;
                max-elements 100;
            }
            list dummy {
                leaf string1 {
                    type string;
                }
                leaf boolean1 {
                    type boolean;
                }
                leaf int2 {
                    type int16;
                }
            }
        }
        container subtree2 {
            leaf-list names {
                type string;
            }
        }
    }
    container operational-data {
        leaf int4 {
            type int32;
        }
    }
}
