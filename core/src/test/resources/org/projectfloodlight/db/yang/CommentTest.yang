module CommentTest {
    /* Here's a multi-line comment.
       Another line.
    */
    /* Embedded multi-line comment start /*  */
    namespace "org.projectfloodlight.db";
    // Single line comment
    prefix "ct";
    //
}
// Final line comment (with no final CR/LF
