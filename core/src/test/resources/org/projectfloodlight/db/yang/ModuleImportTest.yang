module ModuleImportTest {
    namespace org.projectfloodlight.db;
    prefix "mit";
    import BaseTypes {
        prefix a;
    }
    import MoreTypes {
        prefix b;
        revision-date 2012-07-12;
    }
}
