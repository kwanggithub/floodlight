module UnkeyedListTest {
    namespace org.projectfloodlight.db;
    prefix "nlt";
    
    description "Unkeyed list test model";
    
    organization "BigDB Inc.";
    
    extension data-source {
        argument data-source-name;
    }
    
    list unkeyed-list {
        nlt:data-source "unkeyed-list";
        config false;
        leaf name { type string; }
        leaf counter { type int64; }
    }
}
