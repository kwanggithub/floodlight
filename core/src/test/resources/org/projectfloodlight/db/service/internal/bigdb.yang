module bigdb {
    namespace org.projectfloodlight.db;
    prefix "bigdb";

    description "Definitions to work with BigDB";

    organization "www.openflowhub.org";

    extension data-source {
        description "Extension to specify the data source for a node";
        argument data-source-name;
    }

    extension information-type {
        description
            "Extension to specify the type of information.

            Can have values as debug, default-no-return";
        argument information-type-name;
    }

    extension column-header {
        description "String value to use as the column header";
        argument column-header-name;
    }

    extension case-sensitive {
        description "identify field value as case sensitive, default True";
        argument case-sensitive-value;
    }

    extension alias {
        description "identify this field as an alias for the key, default False";
        argument alias-value;
    }

    extension allow-empty-string {
        description
            "Boolean value that indicates that the value for a string leaf node
             is allowed to be an empty string. If the allow-empty-string value
             is true, then when the string value is set to the empty string it
             is not validated against the restrictions (e.g. length, patterns)
             specified in the schema. The default value is false.";
        argument allow-empty-string-value;
    }
}
